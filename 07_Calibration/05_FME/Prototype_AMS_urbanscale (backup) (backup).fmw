FME workspace Prototype_AMS_urbanscale (backup) (backup).fmw
Title: Prototype_AMS

Parameters:
- SourceDataset_LAS_9 = C:\Users\IA\Desktop\ahn3\LAS_testbed.las   # Source ASPRS LAS File(s)
- SourceDataset_WFS_22 = https://geodata.nationaalgeoregister.nl/bag/wfs?&request=GetCapabilities&service=WFS   # Source WFS (Web Feature Service) URL
- SourceDataset_CSV2 = C:\Users\IA\Google Drive\Master Studies\03. TU Delft\09. Graduation\spatio-temporal-analysis\01_Datasets\01_GISLayers\Amsterdam\buildingTables\ResidentialBuildingID_training.csv   # Source CSV (Comma Separated Value) File(s)
- SourceDataset_LAS_6 = C:\Users\IA\Desktop\ahn3\C_25GN1.LAZ   # Source ASPRS LAS File(s)
- DestDataset_GML = C:\Users\IA\Google Drive\Master Studies\03. TU Delft\09. Graduation\spatio-temporal-analysis\01_Datasets\01_GISLayers\Amsterdam\pc6_training.xml   # Destination Geography Markup Language (GML) File
- DestDataset_CSV2 = C:\Users\IA\Google Drive\Master Studies\03. TU Delft\09. Graduation\spatio-temporal-analysis\01_Datasets\01_GISLayers\Amsterdam\buildingTables   # Destination CSV (Comma Separated Value) Folder
- SourceDataset_GML = C:\Users\IA\Google Drive\Master Studies\03. TU Delft\09. Graduation\spatio-temporal-analysis\01_Datasets\01_GISLayers\Amsterdam\building_clipped_training.gml   # Source Geography Markup Language (GML) File(s)
- DestDataset_SKP_7 = C:\Users\IA\Google Drive\Master Studies\03. TU Delft\09. Graduation\spatio-temporal-analysis\01_Datasets\02_CityModels\AMS_skpModel   # Destination Trimble SketchUp Folder
- DestDataset_SKP_6 = C:\Users\IA\Google Drive\Master Studies\03. TU Delft\09. Graduation\spatio-temporal-analysis\01_Datasets\02_CityModels\AMS_skpModel   # Destination Trimble SketchUp Folder
- DestDataset_SKP_8 = C:\Users\IA\Google Drive\Master Studies\03. TU Delft\09. Graduation\spatio-temporal-analysis\01_Datasets\02_CityModels\AMS_skpModel   # Destination Trimble SketchUp Folder
- SourceDataset_ESRISHAPE = C:\Users\IA\Google Drive\Master Studies\03. TU Delft\09. Graduation\spatio-temporal-analysis\08_Archetype\02_Datasets\building_footprint\Arch_BuildingFootprint.shp   # Source Esri Shapefile(s)
- DestDataset_SKP = C:\Users\IA\Google Drive\Master Studies\03. TU Delft\09. Graduation\spatio-temporal-analysis\08_Archetype\02_Datasets\LoD1 models   # Destination Trimble SketchUp Folder
- SourceDataset_GML_6 = C:\Users\IA\Google Drive\Master Studies\03. TU Delft\09. Graduation\spatio-temporal-analysis\01_Datasets\01_GISLayers\Amsterdam\address_clipped_training.gml   # Source Geography Markup Language (GML) File(s)
- SourceDataset_GML_9 = C:\Users\IA\Google Drive\Master Studies\03. TU Delft\09. Graduation\spatio-temporal-analysis\08_Archetype\02_Datasets\building_footprint\Arch_BuildingFootprint.gml   # Source Geography Markup Language (GML) File(s)
- DestDataset_LAS = C:\Users\IA\Google Drive\Master Studies\03. TU Delft\09. Graduation\spatio-temporal-analysis\08_Archetype\02_Datasets\pointcloud   # Destination ASPRS LAS Folder
- SourceDataset_ESRISHAPE_11 = C:\Users\IA\Google Drive\Master Studies\03. TU Delft\09. Graduation\spatio-temporal-analysis\08_Archetype\02_Datasets\building_footprint\Archetype_AoI.shp   # Source Esri Shapefile(s)
- DestDataset_ESRISHAPE_5 = C:\Users\IA\Google Drive\Master Studies\03. TU Delft\09. Graduation\spatio-temporal-analysis\08_Archetype\02_Datasets\building_footprint   # Destination Esri Shapefile Folder
- SourceDataset_LAS = C:\Users\IA\Google Drive\Master Studies\03. TU Delft\09. Graduation\spatio-temporal-analysis\08_Archetype\02_Datasets\pointcloud\LAS_AMS_Noord.las   # Source ASPRS LAS File(s)
- SourceDataset_ESRISHAPE_17 = C:\Users\IA\Google Drive\Master Studies\03. TU Delft\09. Graduation\spatio-temporal-analysis\08_Archetype\02_Datasets\building_footprint\Archetype_AoI.shp   # Source Esri Shapefile(s)
- DestDataset_ESRISHAPE_2 = C:\Users\IA\Google Drive\Master Studies\03. TU Delft\09. Graduation\spatio-temporal-analysis\09_Calibration\04_BuildingData   # Destination Esri Shapefile Folder
- DestDataset_ESRISHAPE_4 = C:\Users\IA\Google Drive\Master Studies\03. TU Delft\09. Graduation\spatio-temporal-analysis\09_Calibration\04_BuildingData   # Destination Esri Shapefile Folder
- SourceDataset_ESRISHAPE_21 = C:\Users\IA\Google Drive\Master Studies\03. TU Delft\09. Graduation\spatio-temporal-analysis\08_Archetype\02_Datasets\building_footprint\BuildingFootprint_final.shp   # Source Esri Shapefile(s)
- SourceDataset_ESRISHAPE_19 = C:\Users\IA\Google Drive\Master Studies\03. TU Delft\09. Graduation\spatio-temporal-analysis\09_Calibration\04_BuildingData\BuildingFootprint_cleaned.shp   # Source Esri Shapefile(s)
- SourceDataset_ESRISHAPE_18 = C:\Users\IA\Google Drive\Master Studies\03. TU Delft\09. Graduation\spatio-temporal-analysis\09_Calibration\04_BuildingData\BuildingFootprint_final_All.shp   # Source Esri Shapefile(s)
- SourceDataset_ESRISHAPE_13 = C:\Users\IA\Google Drive\Master Studies\03. TU Delft\09. Graduation\spatio-temporal-analysis\08_Archetype\02_Datasets\building_footprint\BuildingFootprint_raw.shp   # Source Esri Shapefile(s)
- SourceDataset_ESRISHAPE_16 = C:\Users\IA\Google Drive\Master Studies\03. TU Delft\09. Graduation\spatio-temporal-analysis\08_Archetype\02_Datasets\building_footprint\Archetype_AoI_small.shp   # Source Esri Shapefile(s)
- DestDataset_GML_2 = C:\Users\IA\Google Drive\Master Studies\03. TU Delft\09. Graduation\spatio-temporal-analysis\08_Archetype\02_Datasets\building_footprint\AddressLayer\Address_raw.gml   # Destination Geography Markup Language (GML) File
- SourceDataset_GML_8 = C:\Users\IA\Google Drive\Master Studies\03. TU Delft\09. Graduation\spatio-temporal-analysis\09_Calibration\04_BuildingData\AddressLayer\Address_raw.gml   # Source Geography Markup Language (GML) File(s)
- SourceDataset_POSTGRES = AMSdb   # Connection
- DestDataset_ESRISHAPE_6 = C:\Users\IA\Google Drive\Master Studies\03. TU Delft\09. Graduation\spatio-temporal-analysis\09_Calibration\04_BuildingData   # Destination Esri Shapefile Folder
- SourceDataset_GML_7 = C:\Users\IA\Google Drive\Master Studies\03. TU Delft\09. Graduation\spatio-temporal-analysis\08_Archetype\02_Datasets\building_footprint\Arch_BuildingFootprint.gml   # Source Geography Markup Language (GML) File(s)
- SourceDataset_POSTGRES_3 = AMSdb   # Connection
- SourceDataset_ESRISHAPE_15 = C:\Users\IA\Google Drive\Master Studies\03. TU Delft\09. Graduation\spatio-temporal-analysis\09_Calibration\04_BuildingData\BuildingBase_calibration.shp   # Source Esri Shapefile(s)
- DestDataset_ESRISHAPE_3 = C:\Users\IA\Google Drive\Master Studies\03. TU Delft\09. Graduation\spatio-temporal-analysis\09_Calibration\04_BuildingData   # Destination Esri Shapefile Folder
- DestDataset_ESRISHAPE_7 = C:\Users\IA\Google Drive\Master Studies\03. TU Delft\09. Graduation\spatio-temporal-analysis\09_Calibration\04_BuildingData   # Destination Esri Shapefile Folder
- DestDataset_POSTGRES = AMSdb   # Connection
- SourceDataset_ESRISHAPE_20 = C:\Users\IA\Google Drive\Master Studies\03. TU Delft\09. Graduation\spatio-temporal-analysis\09_Calibration\04_BuildingData\BuildingBase_small_generalized.shp   # Source Esri Shapefile(s)
- FEATURE_TYPES_2 =
- SourceDataset_POSTGRES_6 = AMSdb   # Connection
- FEATURE_TYPES_3 = public.CS_geometry
- SourceDataset_ESRISHAPE_12 = C:\Users\IA\Google Drive\Master Studies\03. TU Delft\09. Graduation\spatio-temporal-analysis\09_Calibration\04_BuildingData\BuildingBase_generalized.shp   # Source Esri Shapefile(s)
- FEATURE_TYPES_4 =
- SourceDataset_POSTGRES_7 = AMSdb   # Connection
- FEATURE_TYPES = public.Calibration_results

Readers:
- LAS_1: LAS from $(SourceDataset_LAS_6) in EPSG:28992
- LAS_2: LAS from $(SourceDataset_LAS_9) in EPSG:28992
- WFS_1: WFS from $(SourceDataset_WFS_22) in EPSG:28992
- CSV2_1: CSV2 from $(SourceDataset_CSV2) in EPSG:28992
- GML_1: GML from $(SourceDataset_GML) in EPSG:28992
- GML_2: GML from $(SourceDataset_GML_6) in EPSG:28992
- GML_3: GML from $(SourceDataset_GML_9) in EPSG:28992
- GML_4: GML from $(SourceDataset_GML_7) in EPSG:28992
- ESRISHAPE_1: ESRISHAPE from $(SourceDataset_ESRISHAPE) in EPSG:28992
- ESRISHAPE_2: ESRISHAPE from $(SourceDataset_ESRISHAPE_11) in EPSG:28992
- ESRISHAPE_3: ESRISHAPE from $(SourceDataset_ESRISHAPE_17) in EPSG:28992
- ESRISHAPE_4: ESRISHAPE from $(SourceDataset_ESRISHAPE_13) in EPSG:28992
- LAS_3: LAS from $(SourceDataset_LAS) in EPSG:28992
- ESRISHAPE_5: ESRISHAPE from $(SourceDataset_ESRISHAPE_16) in EPSG:28992
- ESRISHAPE_6: ESRISHAPE from $(SourceDataset_ESRISHAPE_21) in EPSG:28992
- ESRISHAPE_7: ESRISHAPE from $(SourceDataset_ESRISHAPE_19) in EPSG:28992
- ESRISHAPE_8: ESRISHAPE from $(SourceDataset_ESRISHAPE_18) in EPSG:28992
- GML_5: GML from $(SourceDataset_GML_8) in EPSG:28992
- POSTGRES_1: POSTGRES from $(SourceDataset_POSTGRES) in EPSG:28992
- ESRISHAPE_9: ESRISHAPE from $(SourceDataset_ESRISHAPE_15) in EPSG:28992
- POSTGRES_2: POSTGRES from $(SourceDataset_POSTGRES_3) in EPSG:28992
- ESRISHAPE_14: ESRISHAPE from $(SourceDataset_ESRISHAPE_20) in EPSG:28992
- POSTGRES_5: POSTGRES from $(SourceDataset_POSTGRES_6) in EPSG:28992
- ESRISHAPE_10: ESRISHAPE from $(SourceDataset_ESRISHAPE_12) in EPSG:28992
- POSTGRES_4: POSTGRES from $(SourceDataset_POSTGRES_7)

Writers:
- GML_6: GML to $(DestDataset_GML) in EPSG:28992
- CSV2_2: CSV2 to $(DestDataset_CSV2) in EPSG:28992
- SKP_1: SKP to $(DestDataset_SKP_7) in EPSG:28992
- SKP_2: SKP to $(DestDataset_SKP_6) in EPSG:28992
- SKP_3: SKP to $(DestDataset_SKP_8) in EPSG:28992
- SKP_4: SKP to $(DestDataset_SKP) in EPSG:28992
- LAS_4: LAS to $(DestDataset_LAS) in EPSG:28992
- ESRISHAPE_11: ESRISHAPE to $(DestDataset_ESRISHAPE_5) in EPSG:28992
- ESRISHAPE_12: ESRISHAPE to $(DestDataset_ESRISHAPE_2) in EPSG:28992
- ESRISHAPE_13: ESRISHAPE to $(DestDataset_ESRISHAPE_4) in EPSG:28992
- GML_7: GML to $(DestDataset_GML_2) in EPSG:28992
- ESRISHAPE_15: ESRISHAPE to $(DestDataset_ESRISHAPE_6) in EPSG:28992
- ESRISHAPE_16: ESRISHAPE to $(DestDataset_ESRISHAPE_3) in EPSG:28992
- ESRISHAPE_17: ESRISHAPE to $(DestDataset_ESRISHAPE_7) in EPSG:28992
- POSTGRES_3: POSTGRES to $(DestDataset_POSTGRES) in EPSG:28992

Note: 1st step: prepare point cloud for AoI
Archetype_AoI (reader ESRISHAPE_2) [off]
    attributes: id long
    -> Aggregator_2 [off]
Note: 2nd step: prepare base layer / Pand and verblijfsobject WFS requests need to be carried out separately to aovid conflict error
LAS (reader LAS_1) [off]
    -> PointCloudThinner [off]
Archetype_AoI (reader ESRISHAPE_3) [off]
    attributes: id long
    -> Aggregator [off]
Note: 2DForcer_2 : Input
Note: 3rd step: clean baselayer and add additional attribute: adjaceny and residential / This step identifies artifacts, non-residential building, and count building adjacency
Junction_3 [off]
    -> Junction_4 [off]
BuildingFootprint_raw (reader ESRISHAPE_4) [off]
    attributes: gml_parent char(254), gml_pare00 char(254), gml_id char(254), identifica number(31,15), identifi00 logical, bouwjaar number(31,15), bouwjaar_x logical, status char(254), status_xsi logical, gebruiksdo char(254), gebruiks00 logical, oppervlakt number(31,15), oppervla00 logical, oppervla01 number(31,15), oppervla02 logical, aantal_ver number(20,0), aantal_v00 logical, actualitei char(254), actualit00 logical, geometrie char(254), _clipped char(200)
    -> AreaGapAndOverlapCleaner
BuildingFootprint_cleaned (writer ESRISHAPE_12) [off]
    attributes: bouwjaar number(31,15), status char(254), residentia char(200), identifica number(31,15), gebruiksdo char(254), oppervlakt number(31,15), aantal_ver number(20,0), Number_of_ char(200), semi_detac char(200), dwelling_t char(200), simplified char(200)
Inspector_10 [off]
BuildingFootprint_cleaned (reader ESRISHAPE_7) [off]
    attributes: bouwjaar number(31,15), status char(254), residentia char(200), identifica number(31,15), gebruiksdo char(254), oppervlakt number(31,15), aantal_ver number(20,0), Number_of_ char(200), semi_detac char(200), dwelling_t char(200), simplified char(200)
    -> Junction_7
    -> GeometryExtractor_2
Junction_7
    -> AttributeManager_5
LAS (reader LAS_3) [off]
    -> PointCloudFilter_2
LoD1_AMS_small (writer SKP_4) [off]
BuildingFootprint_final_All (writer ESRISHAPE_13) [off]
    attributes: identifica number(31,15), semi_detac char(200), dwelling_t char(200), simplified char(200), constructi char(200), status char(254), z_median char(200), volume char(200), building_h char(200), ground_hei char(200), residentia char(200), sketchup_l char(200), gebruiksdo char(254), oppervlakt number(31,15), aantal_ver number(20,0), Number_of_ char(200)
Inspector_14 [off]
Inspector_12 [off]
BuildingFootprint_final_All (reader ESRISHAPE_8) [off]
    attributes: identifica number(31,15), semi_detac char(200), dwelling_t char(200), simplified char(200), constructi char(200), status char(254), z_median char(200), volume char(200), building_h char(200), ground_hei char(200), residentia char(200), sketchup_l char(200), gebruiksdo char(254), oppervlakt number(31,15), aantal_ver number(20,0), Number_of_ char(200)
    -> AttributeManager_25
Address_raw (reader GML_5) [off]
    attributes: identificatie xml_real64, identificatie.xsi_nil xml_boolean, oppervlakte xml_real64, oppervlakte.xsi_nil xml_boolean, status xml_buffer, status.xsi_nil xml_boolean, gebruiksdoel xml_buffer, gebruiksdoel.xsi_nil xml_boolean, openbare_ruimte xml_buffer, openbare_ruimte.xsi_nil xml_boolean, huisnummer xml_real64, huisnummer.xsi_nil xml_boolean, huisletter xml_buffer, huisletter.xsi_nil xml_boolean, toevoeging xml_buffer, toevoeging.xsi_nil xml_boolean, postcode xml_buffer, postcode.xsi_nil xml_boolean, woonplaats xml_buffer, woonplaats.xsi_nil xml_boolean, actualiteitsdatum xml_datetime, actualiteitsdatum.xsi_nil xml_boolean, bouwjaar xml_real64, bouwjaar.xsi_nil xml_boolean, pandidentificatie xml_real64, pandidentificatie.xsi_nil xml_boolean, pandstatus xml_buffer, pandstatus.xsi_nil xml_boolean, geometrie xml_geometry, pandgeometrie xml_geometry,
      _clipped xml_char(200)
    -> AttributeManager_18
CBS_pc6_08_10 (reader POSTGRES_1) [off]
    attributes: postcode varchar(80), gemeentecode int4, Oad2010 int4, Sted int4, aantal_inwoners int4, aantal_mannen int4, aantal_vrouwen int4, perc_00_14 int4, perc_15_24 int4, perc_25_44 int4, perc_45_64 int4, perc_65_74 int4, perc_75_ouder int4, nietwestersallochtoon int4, eenpersoonshuishouden_perc int4, eenouderhuishouden_perc int4, meerpzonderkinderen_perc int4, tweeouderhuishouden_perc int4, woningvrd int4, gemwoningwaarde int4, aantal_parthh int4
    -> FeatureMerger_12 [SUPPLIER]
BuildingBase_calibration (writer ESRISHAPE_15) [off]
    attributes: buildingID char(200), dwelling_t char(200), simplified char(200), constructi char(200), status char(254), volume char(200), building_h char(200), residentia char(200), gebruiksdo char(254), oppervlakt number(31,15), aantal_ver number(20,0), Number_of_ char(200), dataComple char(200), postcodes char(200), pandidenti double, building_r char(200), est_occupa char(200), pc6_aantal char(200), pc6_reside char(200)
Inspector_21 [off]
BuildingBase_calibration (reader ESRISHAPE_9) [off]
    attributes: buildingID char(200), dwelling_t char(200), simplified char(200), constructi char(200), status char(254), volume char(200), building_h char(200), residentia char(200), gebruiksdo char(254), oppervlakt number(31,15), aantal_ver number(20,0), Number_of_ char(200), postcodes char(200), pandidenti number(31,15), est_occupa char(200), pc6_aantal char(200), pc6_reside char(200), dataComple char(200), building_r char(200)
    -> TestFilter_5
AttributeManager_50
    -> AttributeManager_60
AttributeManager_49
    -> AttributeManager_60
AttributeManager_11
    -> AttributeManager_60
AttributeManager_57
    -> AttributeManager_60
BuildingBase_generalized (writer ESRISHAPE_17)
    attributes: buildingID char(200), dwelling_t char(200), simplified char(200), constructi char(200), status char(254), volume char(200), building_h char(200), residentia char(200), b_function char(200), b_Area char(200), address_nu char(200), adjacent_b char(200), postcodes char(200), est_b_occu char(200), pc6_popula char(200), pc6_r_area char(200), dataComple char(200), building_r char(200), archetype char(200)
liander2017 (reader POSTGRES_2)
    attributes: responsible varchar(30), grid_operator varchar(30), grid_area varchar(40), street varchar(50), postcode_from varchar(6), postcode_to varchar(6), residence varchar(25), landcode varchar(5), product_type varchar(5), consumption_segment varchar(5), connections_num int4, deliver_direction_perc float8, physical_status_perc float8, final_connection_perc float8, type_connection_perc float8, connection_type varchar(6), avg_annual_consumption int4, sjv_low_rate float8, smart_meter_perc float8, avg_counting_wheels float8
    -> Test_PC6_resgion
BuildingBase_small_generalized (reader ESRISHAPE_14)
    attributes: buildingID char(200), dwelling_t char(200), simplified char(200), constructi char(200), status char(254), volume char(200), building_h char(200), residentia char(200), b_function char(200), b_Area char(200), address_nu char(200), adjacent_b char(200), postcodes char(200), est_b_occu char(200), pc6_popula char(200), pc6_r_area char(200), dataComple char(200), building_r char(200), archetype char(200), _clipped char(200)
    -> TestFilter_10 [off]
    -> Junction_13 [off]
BuildingBase_generalized (reader ESRISHAPE_10)
    attributes: buildingID char(200), dwelling_t char(200), simplified char(200), constructi char(200), status char(254), volume char(200), building_h char(200), residentia char(200), b_function char(200), b_Area char(200), address_nu char(200), adjacent_b char(200), postcodes char(200), est_b_occu char(200), pc6_popula char(200), pc6_r_area char(200), dataComple char(200), building_r char(200), archetype char(200)
    -> TestFilter_10
    -> Junction_13
Candidates: Inspector [off]
Junction_13
    -> FeatureMerger_7 [REQUESTOR]
FeatureMerger_7
    ATTR_ACCUM_MODE = Merge Supplier
    ATTR_CONFLICT_RES = Use Requestor
    IGNORE_NULLS = No
    JOIN_KEYS = @Value(postcodes) @Value(postcodes) AUTO
    MERGE_TYPE = Attributes Only
    PROCESS_DUPS = NO
    REJECT_NULL_MISSING_KEYS = No
    SUPPLIERS_FIRST = No
    MERGED -> Usable
    MERGED -> Junction_14
    UNMERGED_REQUESTOR -> NotUsable
Junction_14
    -> FeatureMerger_16 [REQUESTOR]
Usable: Inspector [off]
NotUsable: Inspector [off]
Archetype_AoI_small (reader ESRISHAPE_5)
    attributes: id long
    -> Clipper_9 [CLIPPER]
Note: BuildingBase_small_generalized: 04_BuildingData [ESRISHAPE] - 4
BuildingBase_small_generalized (writer ESRISHAPE_16)
    attributes: buildingID char(200), dwelling_t char(200), simplified char(200), constructi char(200), status char(254), volume char(200), building_h char(200), residentia char(200), b_function char(200), b_Area char(200), address_nu char(200), adjacent_b char(200), postcodes char(200), est_b_occu char(200), pc6_popula char(200), pc6_r_area char(200), dataComple char(200), building_r char(200), archetype char(200), _clipped char(200)
Note: BuildingBaselayer: AMSdb [POSTGRES] - 3
BuildingBaselayer (writer POSTGRES_3)
    attributes: buildingid varchar(200), dwelling_type varchar(200), simplified_type varchar(200), construction_year varchar(200), status varchar(254), volume varchar(200), building_h varchar(200), residential varchar(200), b_function varchar(200), b_area varchar(200), address_num varchar(200), adjacent_b_num varchar(200), postcodes varchar(200), est_b_occupants varchar(200), pc6_population varchar(200), pc6_r_area varchar(200), datacomplete varchar(200), building_r_area varchar(200), archetype varchar(200), _clipped varchar(200)
Calibration_results (reader POSTGRES_4)
    attributes: buildingID varchar(80), case1_annual_h_wh float8, case2_annual_h_wh float8, case3_annual_h_wh float8, case4_annual_h_wh float8, case5_annual_h_wh float8, case6_annual_h_wh float8, case7_annual_h_wh float8, case8_annual_h_wh float8, case9_annual_h_wh float8, case10_annual_h_wh float8, case11_annual_h_wh float8, case12_annual_h_wh float8, case13_annual_h_wh float8, case14_annual_h_wh float8, case15_annual_h_wh float8, case16_annual_h_wh float8, case17_annual_h_wh float8, case18_annual_h_wh float8, case19_annual_h_wh float8, case20_annual_h_wh float8, case21_annual_h_wh float8, case22_annual_h_wh float8, case23_annual_h_wh float8, case24_annual_h_wh float8, case25_annual_h_wh float8
    -> FeatureMerger_15 [REQUESTOR]
Note: Building volumes
CS_geometry (reader POSTGRES_5)
    attributes: buildingID varchar(80), volume_CitySim float8
    -> FeatureMerger_15 [SUPPLIER]
Inspector_6
Inspector_5
address_clipped_training (reader GML_2) [off]
    attributes: identificatie xml_real64, identificatie.xsi_nil xml_boolean, oppervlakte xml_real64, oppervlakte.xsi_nil xml_boolean, status xml_buffer, status.xsi_nil xml_boolean, gebruiksdoel xml_buffer, gebruiksdoel.xsi_nil xml_boolean, openbare_ruimte xml_buffer, openbare_ruimte.xsi_nil xml_boolean, huisnummer xml_real64, huisnummer.xsi_nil xml_boolean, huisletter xml_buffer, huisletter.xsi_nil xml_boolean, toevoeging xml_buffer, toevoeging.xsi_nil xml_boolean, postcode xml_buffer, postcode.xsi_nil xml_boolean, woonplaats xml_buffer, woonplaats.xsi_nil xml_boolean, actualiteitsdatum xml_datetime, actualiteitsdatum.xsi_nil xml_boolean, bouwjaar xml_real64, bouwjaar.xsi_nil xml_boolean, pandidentificatie xml_real64, pandidentificatie.xsi_nil xml_boolean, pandstatus xml_buffer, pandstatus.xsi_nil xml_boolean, geometrie xml_geometry, pandgeometrie xml_geometry,
      _clipped xml_char(200)
    -> AttributeManager_3 [off]
building_clipped_training (reader GML_1) [off]
    attributes: identificatie xml_real64, identificatie.xsi_nil xml_boolean, bouwjaar xml_real64, bouwjaar.xsi_nil xml_boolean, status xml_buffer, status.xsi_nil xml_boolean, gebruiksdoel xml_buffer, gebruiksdoel.xsi_nil xml_boolean, oppervlakte_min xml_real64, oppervlakte_min.xsi_nil xml_boolean, oppervlakte_max xml_real64, oppervlakte_max.xsi_nil xml_boolean, aantal_verblijfsobjecten xml_int64, aantal_verblijfsobjecten.xsi_nil xml_boolean, actualiteitsdatum xml_datetime, actualiteitsdatum.xsi_nil xml_boolean, geometrie xml_geometry, _clipped xml_char(200)
    -> GeometryExtractor [off]
LAS (reader LAS_2) [off]
    -> PointCloudFilter
Inspector_2 [off]
pc6_training (writer GML_6) [off]
    attributes: addressID xml_char(200), postcode xml_buffer, surface xml_char(200), status xml_buffer, function xml_char(200), construction_year xml_char(200), public_space xml_char(200), house_number xml_char(200), house_letter xml_char(200), house_addition xml_char(200), municipality xml_char(200), buildingID xml_char(200), building_gml_id xml_char(200), building_construction_year xml_char(200), building_status xml_char(200), building_function xml_char(200), building_volume xml_char(200), building_surface_min xml_char(200), building_surface_max xml_char(200), building_number_of_dwellings xml_char(200)
Inspector_7 [off]
AccommodationBuilding_training (writer CSV2_2) [off]
    attributes: addressID string, gml_id string, postcode string, surface string, status string, function string, construction_year string, public_space string, house_number string, house_letter string, house_addition string, municipality string, buildingID string, building_gml_id string, building_construction_year string, building_status string, building_function string, building_volume string, building_surface_min string, building_surface_max string, building_number_of_dwellings string
Note: Matched residential building ID / This will only be available after cleaning / and integrating heterogeneous datasets
CSV (reader CSV2_1) [off]
    attributes: BuildingID string
    -> Junction_5
Note: FeatureMerger_6 : Supplier
Junction_5
    -> Junction_6
Note: CSV
Junction_6
    -> FeatureMerger_6 [SUPPLIER]
Inspector_4 [off]
AMS_Simulated_training (writer SKP_1) [off]
Inspector [off]
AMS_Complete_training (writer SKP_2) [off]
AMS_SimuPlusRest (writer SKP_3) [off]
Inspector_16 [off]
Arch_BuildingFootprint (reader ESRISHAPE_1) [off]
    attributes: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

Bookmark: Prepareing point cloud
Aggregator_2 [off]
    ACCUM_ATTRS_NAME = Use Attributes From One Feature
    AGGREGATE_TYPE = Homogeneous Collection (If Possible)
    ATTR_TO_TRAIT = Yes
    ID_SELECTION = ID and Parent ID
    MODE = Geometry - Assemble One Level
    ORDERED = No
    PRESERVE_ID = No
    SEP = ,
    AGGREGATE -> Bufferer [off]
Bufferer [off]
    ANGLE = 22.5
    CAP_STYLE = Round
    CORNER_STYLE = Round
    OFFSET = 5
    BUFFERED -> Clipper [CLIPPER] [off]
PointCloudThinner [off]
    INTERVAL = 5
    THINNED -> PointCloudCombiner [off]
PointCloudCombiner [off]
    ACCUM_ATTRS_NAME = Yes
    EXTRACT_RASTER_NODATA_NAME = No
    SPACING = 1.0
    -> Clipper [CLIPPEE] [off]
Clipper [off]
    ATTR_ACCUM_MODE = Merge Clipper
    ATTR_CONFLICT_RES = Use Clippee
    BOUNDARY_CASES = Treat as Inside
    CLEANING_TOLERANCE = None
    CLIPPED_ATTR = _clipped
    CLIP_TYPE = Multiple Clippers
    CONNECT_Z_MODE = First Wins
    CREATE_AGGREGATES = Yes
    DEFAULT_VAL = 0
    LINES_AS_SEGMENTS = No
    MEASURE_TYPE = Continuous
    MISSING_VAL_MODE = Compute
    PRESERVE_CLIPPEE_EXTENTS = No
    VAL_SOURCE = Clippee Only
    INSIDE -> Inspector_3 [off]
    INSIDE -> LAS_AMS_Noord (writer LAS_4) [off]
Note: Name is wrong, as AoI is changed
LAS_AMS_Noord (writer LAS_4) [off]
Inspector_3 [off]

Bookmark: Preparing base layers from WFS
Aggregator [off]
    ACCUM_ATTRS_NAME = Use Attributes From One Feature
    AGGREGATE_TYPE = Homogeneous Collection (If Possible)
    ATTR_TO_TRAIT = Yes
    ID_SELECTION = ID and Parent ID
    MODE = Geometry - Assemble One Level
    ORDERED = No
    PRESERVE_ID = No
    SEP = ,
    AGGREGATE -> Junction_3 [off]
    AGGREGATE -> Clipper_2 [CLIPPER] [off]
    AGGREGATE -> Clipper_4 [CLIPPER] [off]
pand (reader WFS_1) [off]
    attributes: gml_parent_id xml_buffer, gml_parent_property xml_buffer, gml_id xml_buffer, identificatie xml_real64, identificatie.xsi_nil xml_boolean, bouwjaar xml_real64, bouwjaar.xsi_nil xml_boolean, status xml_buffer, status.xsi_nil xml_boolean, gebruiksdoel xml_buffer, gebruiksdoel.xsi_nil xml_boolean, oppervlakte_min xml_real64, oppervlakte_min.xsi_nil xml_boolean, oppervlakte_max xml_real64, oppervlakte_max.xsi_nil xml_boolean, aantal_verblijfsobjecten xml_int64, aantal_verblijfsobjecten.xsi_nil xml_boolean, actualiteitsdatum xml_datetime, actualiteitsdatum.xsi_nil xml_boolean, geometrie xml_geometry
    -> Clipper_2 [CLIPPEE] [off]
Clipper_2 [off]
    BOUNDARY_CASES = Treat as Inside
    CLEANING_TOLERANCE = None
    CLIPPED_ATTR = _clipped
    CLIP_TYPE = Single Clipper
    CREATE_AGGREGATES = Yes
    LINES_AS_SEGMENTS = No
    MEASURE_TYPE = Continuous
    MISSING_VAL_MODE = Compute
    PRESERVE_CLIPPEE_EXTENTS = No
    VAL_SOURCE = Clippee Only
    INSIDE -> BuildingFootprint_raw (writer ESRISHAPE_11) [off]
    INSIDE -> Inspector_8 [off]
BuildingFootprint_raw (writer ESRISHAPE_11) [off]
    attributes: gml_parent char(254), gml_pare00 char(254), gml_id char(254), identifica double, identifi00 logical, bouwjaar double, bouwjaar_x logical, status char(254), status_xsi logical, gebruiksdo char(254), gebruiks00 logical, oppervlakt double, oppervla00 logical, oppervla01 double, oppervla02 logical, aantal_ver number(20,0), aantal_v00 logical, actualitei char(254), actualit00 logical, geometrie char(254), _clipped char(200)
Inspector_8 [off]
verblijfsobject (reader WFS_1) [off]
    attributes: gml_parent_id xml_buffer, gml_parent_property xml_buffer, gml_id xml_buffer, identificatie xml_real64, identificatie.xsi_nil xml_boolean, oppervlakte xml_real64, oppervlakte.xsi_nil xml_boolean, status xml_buffer, status.xsi_nil xml_boolean, gebruiksdoel xml_buffer, gebruiksdoel.xsi_nil xml_boolean, openbare_ruimte xml_buffer, openbare_ruimte.xsi_nil xml_boolean, huisnummer xml_real64, huisnummer.xsi_nil xml_boolean, huisletter xml_buffer, huisletter.xsi_nil xml_boolean, toevoeging xml_buffer, toevoeging.xsi_nil xml_boolean, postcode xml_buffer, postcode.xsi_nil xml_boolean, woonplaats xml_buffer, woonplaats.xsi_nil xml_boolean, actualiteitsdatum xml_datetime, actualiteitsdatum.xsi_nil xml_boolean, bouwjaar xml_real64, bouwjaar.xsi_nil xml_boolean, pandidentificatie xml_real64, pandidentificatie.xsi_nil xml_boolean, pandstatus xml_buffer,
      pandstatus.xsi_nil xml_boolean, geometrie xml_geometry, pandgeometrie xml_geometry
    -> Clipper_4 [CLIPPEE] [off]
Clipper_4 [off]
    BOUNDARY_CASES = Treat as Inside
    CLEANING_TOLERANCE = None
    CLIPPED_ATTR = _clipped
    CLIP_TYPE = Single Clipper
    CREATE_AGGREGATES = Yes
    LINES_AS_SEGMENTS = No
    MEASURE_TYPE = Continuous
    MISSING_VAL_MODE = Compute
    PRESERVE_CLIPPEE_EXTENTS = No
    VAL_SOURCE = Clippee Only
    INSIDE -> Inspector_15 [off]
    INSIDE -> Address_raw (writer GML_7) [off]
Address_raw (writer GML_7) [off]
    attributes: identificatie xml_real64, identificatie.xsi_nil xml_boolean, oppervlakte xml_real64, oppervlakte.xsi_nil xml_boolean, status xml_buffer, status.xsi_nil xml_boolean, gebruiksdoel xml_buffer, gebruiksdoel.xsi_nil xml_boolean, openbare_ruimte xml_buffer, openbare_ruimte.xsi_nil xml_boolean, huisnummer xml_real64, huisnummer.xsi_nil xml_boolean, huisletter xml_buffer, huisletter.xsi_nil xml_boolean, toevoeging xml_buffer, toevoeging.xsi_nil xml_boolean, postcode xml_buffer, postcode.xsi_nil xml_boolean, woonplaats xml_buffer, woonplaats.xsi_nil xml_boolean, actualiteitsdatum xml_datetime, actualiteitsdatum.xsi_nil xml_boolean, bouwjaar xml_real64, bouwjaar.xsi_nil xml_boolean, pandidentificatie xml_real64, pandidentificatie.xsi_nil xml_boolean, pandstatus xml_buffer, pandstatus.xsi_nil xml_boolean, geometrie xml_geometry, pandgeometrie xml_geometry,
      _clipped xml_char(200)
Inspector_15 [off]

Bookmark: Extrusion
Note: AoI_AMS
Junction_4
    -> 2DForcer_2
GeometryExtractor [off]
    ATTR = _geometry
    KIND_LONG = FME Binary
    REMOVE_GEOMETRY = No
    -> Clipper_8 [CLIPPER]
PointCloudFilter [off]
    FILTER_TABLE = EXPRESSION_LIST @Component(classification) == 6 ; @Component(classification) == 2 FILTER_ATTRIBUTE __pc_internal_filter_attribute__ FILTER_ATTRIBUTE_VALUES_LIST Building ; Ground
    OUTPUT_UNFILTERED_POINTS = Yes
    Building -> Clipper_8 [CLIPPEE]
    Ground -> TINGenerator [POINTS/LINES]
Clipper_8
    ATTR_ACCUM_MODE = Merge Clipper
    ATTR_CONFLICT_RES = Use Clippee
    BOUNDARY_CASES = Treat as Inside
    CLEANING_TOLERANCE = None
    CLIPPED_ATTR = _clipped
    CLIP_TYPE = Multiple Clippers
    CREATE_AGGREGATES = Yes
    LINES_AS_SEGMENTS = No
    MEASURE_TYPE = Continuous
    MISSING_VAL_MODE = Compute
    PRESERVE_CLIPPEE_EXTENTS = No
    VAL_SOURCE = Clippee Only
    INSIDE -> PointCloudStatisticsCalculator
PointCloudStatisticsCalculator
    POINT_COMPONENTS = "z       MEDIAN "
    -> GeometryReplacer
GeometryReplacer
    KIND_LONG = FME Binary
    REMOVE_ATTRIBUTE = Yes
    SOURCE = @Value(_geometry)
    -> 3DForcer
3DForcer
    KEEPZVAL = Yes
    ZVALATTR = 0
    -> Extruder
Extruder
    DIRECTION = Vertical
    DISTANCE = @Value(z.median)
    EXTRUDED -> VolumeCalculator
    EXTRUDED -> AttributeManager_6
TINGenerator [off]
    TOLERANCE = 200
    TIN_SURFACE -> GeometryCoercer_2
Note: If ground generated by TIN is not desired, turn this off
GeometryCoercer_2 [off]
    GQUERY:
      for $geom in //geometry
      where $geom/count(parent::geometry) = 0
      return number($geom/@fme_id)
    KIND = fme_composite_surface
    COERCED -> 2DForcer_2
2DForcer_2 [off]
    2D -> Orientor [off]
Orientor [off]
    KIND = LEFT_HAND_RULE
    ORIENTED -> Clipper_3 [CLIPPEE] [off]

Bookmark: Clean gap, overlap
AreaGapAndOverlapCleaner
    CLEANING_TOLERANCE = 0.5
    CONNECT_Z_MODE = First Wins
    DEAGGREGATE_INPUT = YES
    FILL_ALL_GAPS = No
    MEASURE_TYPE = Continuous
    MISSING_VAL_MODE = Compute
    REPAIR_METHOD = Longest Boundary
    REPAIRED -> SpatialRelator [Requestor]
    REPAIRED -> SpatialRelator [Supplier]

Bookmark: Topology analysis: identify semi-detached buildings
SpatialRelator
    AGGREGATE_HANDLING = Yes
    CALC_CARD = Yes
    CURVE_BOUNDARY_RULE_PARAM = Default Rule
    LIST_ATTRS_TO_INCLUDE = identifica
    LIST_NAME = _relationships
    PREDICATES = TOUCHES
    SUCCESS_ATTR = Number of adjacency
    -> Test_if_num_adjacency_1
    -> FeatureMerger_8 [SUPPLIER]
    -> Junction_8
Test_if_num_adjacency_1: Tester
    BOOL_OP = OR
    TEST_CLAUSE = TEST @Value(Number of adjacency) = 1
    PASSED -> ListConcatenator
ListConcatenator
    DROP_EMPTY_PARTS = No
    LIST_ATTR = _relationships{}.identifica
    SEP = ,
    VAL_ATTR = _concatenated
    -> AttributeManager_7
AttributeManager_7
    ATTR_TABLE:
      REMOVE gml_parent
      REMOVE gml_pare00
      REMOVE gml_id
      RENAME_SET_VALUE identifica > originalID
      REMOVE identifi00
      REMOVE bouwjaar
      REMOVE bouwjaar_x
      REMOVE status
      REMOVE status_xsi
      REMOVE gebruiksdo
      REMOVE gebruiks00
      REMOVE oppervlakt
      REMOVE oppervla00
      REMOVE oppervla01
      REMOVE oppervla02
      REMOVE aantal_ver
      REMOVE aantal_v00
      REMOVE actualitei
      REMOVE actualit00
      REMOVE geometrie
      REMOVE _clipped
      REMOVE _relationships{}.identifica
      REMOVE _relationships{}.de9im
      REMOVE _relationships{}.pass{}
      REMOVE _relationships{}.card_point
      REMOVE _relationships{}.card_line
      REMOVE _relationships{}.card_area
      REMOVE Number of adjacency
      RENAME_SET_VALUE _concatenated > neighbouringID
    -> FeatureMerger_8 [REQUESTOR]
FeatureMerger_8
    ATTR_ACCUM_MODE = Merge Supplier
    ATTR_CONFLICT_RES = Use Requestor
    IGNORE_NULLS = No
    JOIN_KEYS = @Value(neighbouringID) @Value(identifica) AUTO
    MERGE_TYPE = Attributes Only
    PROCESS_DUPS = NO
    REJECT_NULL_MISSING_KEYS = No
    SUPPLIERS_FIRST = No
    MERGED -> Tester_2
Tester_2
    BOOL_OP = OR
    TEST_CLAUSE = TEST @Value(Number of adjacency) = 1
    PASSED -> AttributeManager_9
AttributeManager_9
    ATTR_TABLE:
      REMOVE neighbouringID
      SET_TO semi_detached = 1
      REMOVE gml_parent
      REMOVE gml_pare00
      REMOVE gml_id
      REMOVE identifica
      REMOVE identifi00
      REMOVE bouwjaar
      REMOVE bouwjaar_x
      REMOVE status
      REMOVE status_xsi
      REMOVE gebruiksdo
      REMOVE gebruiks00
      REMOVE oppervlakt
      REMOVE oppervla00
      REMOVE oppervla01
      REMOVE oppervla02
      REMOVE aantal_ver
      REMOVE aantal_v00
      REMOVE actualitei
      REMOVE actualit00
      REMOVE geometrie
      REMOVE _clipped
      REMOVE _relationships{}.identifica
      REMOVE _relationships{}.de9im
      REMOVE _relationships{}.pass{}
      REMOVE _relationships{}.card_point
      REMOVE _relationships{}.card_line
      REMOVE _relationships{}.card_area
      REMOVE Number of adjacency
    -> FeatureMerger_9 [SUPPLIER]
Junction_8
    -> Junction_9
Junction_9
    -> FeatureMerger_9 [REQUESTOR]
FeatureMerger_9
    ATTR_ACCUM_MODE = Merge Supplier
    ATTR_CONFLICT_RES = Use Requestor
    IGNORE_NULLS = No
    JOIN_KEYS = @Value(identifica) @Value(originalID) AUTO
    MERGE_TYPE = Attributes Only
    PROCESS_DUPS = NO
    REJECT_NULL_MISSING_KEYS = No
    SUPPLIERS_FIRST = No
    MERGED -> Junction_11
    UNMERGED_REQUESTOR -> Junction_10

Bookmark: Dwelling type classification
Junction_11
    -> TestFilter_3
Junction_10
    -> TestFilter_3
Test_SFH_TH_or_MFH: Tester
    BOOL_OP = OR
    TEST_CLAUSE = TEST @Value(aantal_ver) <= 1
    PASSED -> Detached_Tester
    PASSED -> Corner_Tester
    PASSED -> TH_Between_Tester
    FAILED -> Corner_Tester_2
Detached_Tester: Tester
    BOOL_OP = OR
    TEST_CLAUSE = TEST @Value(Number of adjacency) = 0
    PASSED -> AttributeManager_8
Corner_Tester: Tester
    BOOL_OP = OR
    TEST_CLAUSE = TEST @Value(Number of adjacency) = 1
    PASSED -> SemiDetached_Tester
SemiDetached_Tester: Tester
    BOOL_OP = OR
    TEST_CLAUSE = TEST semi_detached ATTRIBUTE_HAS_A_VALUE ""
    PASSED -> AttributeManager_10
    FAILED -> AttributeManager_13
TH_Between_Tester: Tester
    BOOL_OP = OR
    TEST_CLAUSE = TEST @Value(Number of adjacency) >= 2
    PASSED -> AttributeManager_23
Corner_Tester_2: Tester
    BOOL_OP = OR
    TEST_CLAUSE = TEST @Value(Number of adjacency) >= 1
    PASSED -> AttributeManager_15
    FAILED -> AttributeManager_16
AttributeManager_22
    ATTR_TABLE:
      REMOVE gml_id
      REMOVE geometrie
      REMOVE _clipped
      REMOVE gml_parent
      REMOVE gml_pare00
      REMOVE identifi00
      REMOVE bouwjaar_x
      REMOVE status_xsi
      REMOVE gebruiks00
      REMOVE oppervla00
      REMOVE oppervla01
      REMOVE oppervla02
      REMOVE aantal_v00
      REMOVE actualitei
      REMOVE actualit00
      REMOVE _relationships{}.identifica
      REMOVE _relationships{}.de9im
      REMOVE _relationships{}.pass{}
      REMOVE _relationships{}.card_point
      REMOVE _relationships{}.card_line
      REMOVE _relationships{}.card_area
      REMOVE originalID
    -> Inspector_10
    -> BuildingFootprint_cleaned (writer ESRISHAPE_12)

Bookmark: Residential, non-residential building
TestFilter_3
    DEFAULT_VALUE = <UNFILTERED>
    TEST_LIST = "BOOL_OP,OR,COMPOSITE_TEST,""""""<Unused>"""""",TEST_CLAUSE,TEST @Value(gebruiksdo) = woonfunctie",residential building
    residential building -> AttributeManager_12
    <UNFILTERED> -> AttributeManager_14
AttributeManager_12
    ATTR_TABLE = SET_TO residential = 1
    -> Test_SFH_TH_or_MFH
AttributeManager_14
    ATTR_TABLE = SET_TO residential = 0
    -> AttributeManager_17

Bookmark: SFH
AttributeManager_8
    ATTR_TABLE = SET_TO dwelling_type = Detached
    -> AttributeManager_20
AttributeManager_10
    ATTR_TABLE = SET_TO dwelling_type = SemiDetached
    -> AttributeManager_20
AttributeManager_20
    ATTR_TABLE = SET_TO simplified_type = SFH
    -> AttributeManager_22

Bookmark: TH
AttributeManager_13
    ATTR_TABLE = SET_TO dwelling_type = TH_Corner
    -> AttributeManager_19
AttributeManager_23
    ATTR_TABLE = SET_TO dwelling_type = TH_Between
    -> AttributeManager_19
AttributeManager_19
    ATTR_TABLE = SET_TO simplified_type = TH
    -> AttributeManager_22

Bookmark: MFH
AttributeManager_15
    ATTR_TABLE = SET_TO dwelling_type = GalleryComplex
    -> AttributeManager_21
AttributeManager_16
    ATTR_TABLE = SET_TO dwelling_type = Apartment
    -> AttributeManager_21
AttributeManager_21
    ATTR_TABLE = SET_TO simplified_type = MFH
    -> AttributeManager_22

Bookmark: Others
AttributeManager_17
    ATTR_TABLE = SET_TO dwelling_type = Others
    -> AttributeManager_24
AttributeManager_24
    ATTR_TABLE = SET_TO simplified_type = others
    -> AttributeManager_22

Bookmark: Adding building height and volume
GeometryExtractor_2
    ATTR = _geometry
    KIND_LONG = FME Binary
    REMOVE_GEOMETRY = No
    -> Clipper_5 [CLIPPER]
    -> Bufferer_2
    -> Clipper_6 [CLIPPER]
AttributeManager_5
    ATTR_TABLE:
      REMOVE bouwjaar
      REMOVE status
      REMOVE residentia
      REMOVE gebruiksdo
      REMOVE oppervlakt
      REMOVE aantal_ver
      REMOVE Number_of_
    -> FeatureMerger_3 [REQUESTOR]
PointCloudFilter_2
    FILTER_TABLE = EXPRESSION_LIST @Component(classification) == 6 ; @Component(classification) == 2 FILTER_ATTRIBUTE __pc_internal_filter_attribute__ FILTER_ATTRIBUTE_VALUES_LIST Building ; Ground
    OUTPUT_UNFILTERED_POINTS = Yes
    Building -> Clipper_5 [CLIPPEE]
    Ground -> Clipper_7 [CLIPPEE]
FeatureMerger_2
    ATTR_ACCUM_MODE = Merge Supplier
    ATTR_CONFLICT_RES = Use Requestor
    IGNORE_NULLS = No
    JOIN_KEYS = @Value(identifica) @Value(identifica) AUTO
    MERGE_TYPE = Attributes Only
    PROCESS_DUPS = NO
    REJECT_NULL_MISSING_KEYS = No
    SUPPLIERS_FIRST = No
    MERGED -> GeometryReplacer_2
AttributeManager_4
    ATTR_TABLE:
      RENAME_SET_VALUE bouwjaar > construction_year
      REMOVE _clipped
      REMOVE fme_basename
      RENAME_SET_VALUE _volume > volume
      SET_TO building_height = @sub(@Value(z.median),@Value(ground_height))
      REMOVE _fme_no_clipper
      RENAME_SET_VALUE residentia > residential
      RENAME_SET_VALUE identifica > sketchup_layer_name
      RENAME_SET_VALUE Number_of_ > Number_of_adjacency
    -> GeometryPropertySetter_3
    -> FeatureMerger_3 [SUPPLIER]
FeatureMerger_3
    ATTR_ACCUM_MODE = Merge Supplier
    ATTR_CONFLICT_RES = Use Requestor
    IGNORE_NULLS = No
    JOIN_KEYS = @Value(identifica) @Value(sketchup_layer_name) AUTO
    MERGE_TYPE = Attributes Only
    PROCESS_DUPS = NO
    REJECT_NULL_MISSING_KEYS = No
    SUPPLIERS_FIRST = No
    MERGED -> BuildingFootprint_final_All (writer ESRISHAPE_13)
    MERGED -> Inspector_14
    UNMERGED_REQUESTOR -> Inspector_12

Bookmark: Ground height information
Bufferer_2
    ANGLE = 22.5
    CAP_STYLE = Round
    CORNER_STYLE = Round
    MODE = AREA
    OFFSET = 2
    BUFFERED -> Clipper_6 [CLIPPEE]
Clipper_6
    ATTR_ACCUM_MODE = Merge Clipper
    ATTR_CONFLICT_RES = Use Clippee
    BOUNDARY_CASES = Treat as Inside
    CLEANING_TOLERANCE = None
    CLIPPED_ATTR = _clipped
    CLIP_TYPE = Multiple Clippers
    CONNECT_Z_MODE = First Wins
    CREATE_AGGREGATES = Yes
    LINES_AS_SEGMENTS = No
    MEASURE_TYPE = Continuous
    MISSING_VAL_MODE = Compute
    PRESERVE_CLIPPEE_EXTENTS = No
    VAL_SOURCE = Clippee Only
    OUTSIDE -> Clipper_7 [CLIPPER]
Clipper_7
    ATTR_ACCUM_MODE = Merge Clipper
    ATTR_CONFLICT_RES = Use Clippee
    BOUNDARY_CASES = Treat as Inside
    CLEANING_TOLERANCE = None
    CLIPPED_ATTR = _clipped
    CLIP_TYPE = Multiple Clippers
    CREATE_AGGREGATES = Yes
    LINES_AS_SEGMENTS = No
    MEASURE_TYPE = Continuous
    MISSING_VAL_MODE = Compute
    PRESERVE_CLIPPEE_EXTENTS = No
    VAL_SOURCE = Clippee Only
    INSIDE -> PointCloudStatisticsCalculator_3
PointCloudStatisticsCalculator_3
    POINT_COMPONENTS = "z   MEAN     "
    -> Adding_ground_height
Adding_ground_height: AttributeManager
    ATTR_TABLE = RENAME_SET_VALUE z.mean > ground_height
    -> FeatureMerger_2 [SUPPLIER]

Bookmark: Building height information
Clipper_5
    ATTR_ACCUM_MODE = Merge Clipper
    ATTR_CONFLICT_RES = Use Clippee
    BOUNDARY_CASES = Treat as Inside
    CLEANING_TOLERANCE = None
    CLIPPED_ATTR = _clipped
    CLIP_TYPE = Multiple Clippers
    CREATE_AGGREGATES = Yes
    LINES_AS_SEGMENTS = No
    MEASURE_TYPE = Continuous
    MISSING_VAL_MODE = Compute
    PRESERVE_CLIPPEE_EXTENTS = No
    VAL_SOURCE = Clippee Only
    INSIDE -> PointCloudStatisticsCalculator_2
PointCloudStatisticsCalculator_2
    POINT_COMPONENTS = "z       MEDIAN "
    -> FeatureMerger_2 [REQUESTOR]

Bookmark: Extrude LoD1 model and calculate volume
GeometryReplacer_2
    KIND_LONG = FME Binary
    REMOVE_ATTRIBUTE = Yes
    SOURCE = @Value(_geometry)
    -> 3DForcer_2
3DForcer_2
    KEEPZVAL = Yes
    ZVALATTR = @Value(ground_height)
    -> Extruder_2
Extruder_2
    DIRECTION = Vertical
    DISTANCE = @Value(z.median)
    EXTRUDED -> VolumeCalculator_2
VolumeCalculator_2
    MULT = 1
    SET_TRAIT = No
    VOLUME_ATTR = _volume
    -> AttributeManager_4

Bookmark: Skp output port
GeometryPropertySetter_3
    OVERWRITE_CHOICE = Yes
    REMOVE_ATTRIBUTE = No
    SETTYPE_PARAM = Traits From Attributes
    SRC_ATTRS = sketchup_layer_name
    SET -> LoD1_AMS_small (writer SKP_4)

Bookmark: Attach postcode info. to the buildings and estimate building occupant number
AttributeManager_25
    ATTR_TABLE:
      RENAME_SET_VALUE identifica > buildingID
      REMOVE semi_detac
      REMOVE z_median
      REMOVE ground_hei
      REMOVE sketchup_l
    -> FeatureMerger_11 [REQUESTOR]
AttributeManager_18
    ATTR_TABLE:
      REMOVE gml_parent_id
      REMOVE gml_parent_property
      REMOVE gml_id
      REMOVE identificatie
      REMOVE identificatie.xsi_nil
      REMOVE oppervlakte.xsi_nil
      REMOVE status
      REMOVE status.xsi_nil
      REMOVE gebruiksdoel.xsi_nil
      REMOVE openbare_ruimte
      REMOVE openbare_ruimte.xsi_nil
      REMOVE huisnummer
      REMOVE huisnummer.xsi_nil
      REMOVE huisletter
      REMOVE huisletter.xsi_nil
      REMOVE toevoeging
      REMOVE toevoeging.xsi_nil
      REMOVE postcode.xsi_nil
      REMOVE woonplaats
      REMOVE woonplaats.xsi_nil
      REMOVE actualiteitsdatum
      REMOVE actualiteitsdatum.xsi_nil
      REMOVE bouwjaar
      REMOVE bouwjaar.xsi_nil
      REMOVE pandidentificatie.xsi_nil
      REMOVE pandstatus
      REMOVE pandstatus.xsi_nil
      REMOVE geometrie
      REMOVE pandgeometrie
      REMOVE _clipped
    -> FeatureMerger_12 [REQUESTOR]
    -> TestFilter_2
    -> AttributeManager_29
Others: AttributeManager
    ATTR_TABLE = SET_TO dataCompleteness = others
    -> Inspector_21
    -> BuildingBase_calibration (writer ESRISHAPE_15)
FeatureMerger_10
    ATTR_ACCUM_MODE = Merge Supplier
    ATTR_CONFLICT_RES = Use Requestor
    IGNORE_NULLS = No
    JOIN_KEYS = @Value(buildingID) @Value(pandidentificatie) AUTO
    MERGE_TYPE = Attributes Only
    PROCESS_DUPS = NO
    REJECT_NULL_MISSING_KEYS = No
    SUPPLIERS_FIRST = No
    MERGED -> TestDataCompleteness
    UNMERGED_REQUESTOR -> TestDataCompleteness
TestDataCompleteness: TestFilter
    DEFAULT_VALUE = <UNFILTERED>
    TEST_LIST = "BOOL_OP,OR,COMPOSITE_TEST,""""""<Unused>"""""",TEST_CLAUSE,TEST @StringLength(@Value(postcodes)) > 6",@StringLength(@Value(postcodes)) > 6,"BOOL_OP,OR,COMPOSITE_TEST,""""""<Unused>"""""",TEST_CLAUSE,TEST est_occupants ATTRIBUTE_IS_EMPTY """,noOccupantsData
    @StringLength(@Value(postcodes)) > 6 -> FeatureColorSetter
    <UNFILTERED> -> SimulatedBuilding
    noOccupantsData -> NoOccupantsData
FeatureColorSetter
    FILL_COLOR = 1,0.164706,0.176471
    MODE = Fixed
    COLORED -> MultiPostcodes
MultiPostcodes: AttributeManager
    ATTR_TABLE:
      REMOVE pc6{}.postcode
      SET_TO dataCompleteness = multi_postcodes
    -> Inspector_21
    -> BuildingBase_calibration (writer ESRISHAPE_15)
NoOccupantsData: AttributeManager
    ATTR_TABLE:
      SET_TO dataCompleteness = noOccupantsData
      REMOVE pc6{}.postcode
    -> Inspector_21
    -> BuildingBase_calibration (writer ESRISHAPE_15)
SimulatedBuilding: AttributeManager
    ATTR_TABLE:
      REMOVE pc6{}.postcode
      SET_TO dataCompleteness = 1
    -> Inspector_21
    -> BuildingBase_calibration (writer ESRISHAPE_15)

Bookmark: Attach postcode information to the buildings
AttributeManager_29
    ATTR_TABLE:
      REMOVE oppervlakte
      REMOVE gebruiksdoel
    -> FeatureMerger_11 [SUPPLIER]
FeatureMerger_11
    ATTR_ACCUM_MODE = Merge Supplier
    ATTR_CONFLICT_RES = Use Requestor
    IGNORE_NULLS = No
    JOIN_KEYS = @Value(buildingID) @Value(pandidentificatie) AUTO
    LIST_ATTRS_TO_INCLUDE = postcode
    LIST_NAME = pc6
    MERGE_TYPE = Attributes Only
    PROCESS_DUPS = NO
    REJECT_NULL_MISSING_KEYS = No
    SUPPLIERS_FIRST = No
    MERGED -> ListDuplicateRemover
    UNMERGED_REQUESTOR -> Others
ListDuplicateRemover
    SRC_LIST = pc6{}.postcode
    -> PC6_concatenator
PC6_concatenator: ListConcatenator
    DROP_EMPTY_PARTS = No
    LIST_ATTR = pc6{}.postcode
    SEP = ,
    VAL_ATTR = postcodes
    -> AttributeManager_26
AttributeManager_26
    ATTR_TABLE:
      REMOVE postcode
      REMOVE pandidentificatie
    -> FeatureMerger_10 [REQUESTOR]

Bookmark: PC6 residential total area
TestFilter_2
    DEFAULT_VALUE = <UNFILTERED>
    TEST_LIST = "BOOL_OP,OR,COMPOSITE_TEST,""""""<Unused>"""""",TEST_CLAUSE,TEST @Value(gebruiksdoel) = woonfunctie",@Value(gebruiksdoel) = residential
    @Value(gebruiksdoel) = residential -> Aggregator_pc6_area
    @Value(gebruiksdoel) = residential -> Aggregate_building_r_area
Aggregator_pc6_area
    ACCUM_ATTRS_NAME = Use Attributes From One Feature
    AGGREGATE_TYPE = Homogeneous Collection (If Possible)
    GROUP_BY = postcode
    MODE = Geometry - Assemble One Level
    ORDERED = No
    SEP = ,
    SUM = oppervlakte
    AGGREGATE -> AttributeManager_28
AttributeManager_28
    ATTR_TABLE:
      RENAME_SET_VALUE oppervlakte > pc6_residential_area
      REMOVE gebruiksdoel
      REMOVE pandidentificatie
    -> FeatureMerger_13 [SUPPLIER]

Bookmark: Building residential area
Aggregate_building_r_area: Aggregator
    ACCUM_ATTRS_NAME = Use Attributes From One Feature
    AGGREGATE_TYPE = Homogeneous Collection (If Possible)
    GROUP_BY = pandidentificatie
    MODE = Geometry - Assemble One Level
    ORDERED = No
    SEP = ,
    SUM = oppervlakte
    AGGREGATE -> AttributeManager_30
AttributeManager_30
    ATTR_TABLE:
      RENAME_SET_VALUE oppervlakte > building_r_area
      REMOVE gebruiksdoel
      REMOVE postcode
    -> FeatureMerger_14 [REQUESTOR]

Bookmark: Estimate address level occupants
FeatureMerger_12
    ATTR_ACCUM_MODE = Merge Supplier
    ATTR_CONFLICT_RES = Use Requestor
    IGNORE_NULLS = No
    JOIN_KEYS = @Value(postcode) @Value(postcode) AUTO
    MERGE_TYPE = Attributes Only
    PROCESS_DUPS = NO
    REJECT_NULL_MISSING_KEYS = No
    SUPPLIERS_FIRST = No
    MERGED -> Keep_only_relevant_attributes
Keep_only_relevant_attributes: AttributeManager
    ATTR_TABLE:
      REMOVE Oad2010
      REMOVE Sted
      REMOVE aantal_mannen
      REMOVE aantal_vrouwen
      REMOVE perc_00_14
      REMOVE perc_15_24
      REMOVE perc_25_44
      REMOVE perc_45_64
      REMOVE perc_65_74
      REMOVE perc_75_ouder
      REMOVE nietwestersallochtoon
      REMOVE eenpersoonshuishouden_perc
      REMOVE eenouderhuishouden_perc
      REMOVE meerpzonderkinderen_perc
      REMOVE tweeouderhuishouden_perc
      REMOVE woningvrd
      REMOVE gemwoningwaarde
      REMOVE aantal_parthh
    -> TestFilter_4
TestFilter_4
    DEFAULT_VALUE = <UNFILTERED>
    TEST_LIST = "BOOL_OP,OR,COMPOSITE_TEST,""""""<Unused>"""""",TEST_CLAUSE,TEST @Value(gebruiksdoel) = woonfunctie",@Value(gebruiksdoel) = residential
    @Value(gebruiksdoel) = residential -> FeatureMerger_13 [REQUESTOR]
FeatureMerger_13
    ATTR_ACCUM_MODE = Merge Supplier
    ATTR_CONFLICT_RES = Use Requestor
    IGNORE_NULLS = No
    JOIN_KEYS = @Value(postcode) @Value(postcode) AUTO
    MERGE_TYPE = Attributes Only
    PROCESS_DUPS = NO
    REJECT_NULL_MISSING_KEYS = No
    SUPPLIERS_FIRST = No
    MERGED -> est_address_occupants
est_address_occupants: AttributeManager
    ATTR_TABLE:
      REMOVE gemeentecode
      REMOVE gebruiksdoel
      SET_TO est_occupants = @mult(@Value(aantal_inwoners),@div(@Value(oppervlakte),@Value(pc6_residential_area)))
    -> Aggregator_3
Aggregator_3
    ACCUM_ATTRS_NAME = Use Attributes From One Feature
    AGGREGATE_TYPE = Homogeneous Collection (If Possible)
    GROUP_BY = pandidentificatie
    MODE = Geometry - Assemble One Level
    ORDERED = No
    SEP = ,
    SUM = est_occupants
    AGGREGATE -> AttributeManager_27
AttributeManager_27
    ATTR_TABLE:
      SET_TO est_occupants = @round(@Value(est_occupants),0)
      REMOVE oppervlakte
      REMOVE postcode
      RENAME_SET_VALUE aantal_inwoners > pc6_aantal_inwoners
    -> FeatureMerger_14 [SUPPLIER]

Bookmark: Combining residential area and est occupants
FeatureMerger_14
    ATTR_ACCUM_MODE = Merge Supplier
    ATTR_CONFLICT_RES = Use Requestor
    IGNORE_NULLS = No
    JOIN_KEYS = @Value(pandidentificatie) @Value(pandidentificatie) AUTO
    MERGE_TYPE = Attributes Only
    PROCESS_DUPS = NO
    REJECT_NULL_MISSING_KEYS = No
    SUPPLIERS_FIRST = No
    MERGED -> FeatureMerger_10 [SUPPLIER]
    UNMERGED_REQUESTOR -> FeatureMerger_10 [SUPPLIER]

Bookmark: Archetype classification
TestFilter_5
    DEFAULT_VALUE = Others
    TEST_LIST = "BOOL_OP,OR,COMPOSITE_TEST,""""""<Unused>"""""",TEST_CLAUSE,TEST @Value(simplified) = SFH",SFH,"BOOL_OP,OR,COMPOSITE_TEST,""""""<Unused>"""""",TEST_CLAUSE,TEST @Value(simplified) = TH",TH,"BOOL_OP,OR,COMPOSITE_TEST,""""""<Unused>"""""",TEST_CLAUSE,TEST @Value(simplified) = MFH",MFH
    SFH -> Correct_missclassifiedSFH
    TH -> TestFilter_8
    MFH -> TestFilter_7
    Others -> Junction_12
Correct_missclassifiedSFH: TestFilter
    DEFAULT_VALUE = MFH
    TEST_LIST = "BOOL_OP,OR,COMPOSITE_TEST,""""""<Unused>"""""",TEST_CLAUSE,TEST @Value(est_occupa) <= 5",SFH
    SFH -> TestFilter_6
    MFH -> TestFilter_7
TestFilter_6
    DEFAULT_VALUE = <UNFILTERED>
    TEST_LIST = "BOOL_OP,OR,COMPOSITE_TEST,""""""<Unused>"""""",TEST_CLAUSE,TEST @Value(constructi) <= 1964",<=1964,"BOOL_OP,OR,COMPOSITE_TEST,""""""<Unused>"""""",TEST_CLAUSE,NUM_TEST @Value(constructi) RANGE [1965,1974]",1965-1974,"BOOL_OP,OR,COMPOSITE_TEST,""""""<Unused>"""""",TEST_CLAUSE,NUM_TEST @Value(constructi) RANGE [1975,1991]",1975-1991,"BOOL_OP,OR,COMPOSITE_TEST,""""""<Unused>"""""",TEST_CLAUSE,NUM_TEST @Value(constructi) RANGE [1992,2005]",1992-2005,"BOOL_OP,OR,COMPOSITE_TEST,""""""<Unused>"""""",TEST_CLAUSE,NUM_TEST @Value(constructi) RANGE [2006,2014]",2006-2014,"BOOL_OP,OR,COMPOSITE_TEST,""""""<Unused>"""""",TEST_CLAUSE,TEST @Value(constructi) >= 2015",>=2015
    <=1964 -> AttributeManager_37
    1965-1974 -> AttributeManager_38
    1975-1991 -> AttributeManager_39
    1992-2005 -> AttributeManager_40
    2006-2014 -> AttributeManager_41
    >=2015 -> AttributeManager_42
AttributeManager_37
    ATTR_TABLE = SET_TO archetpye = SFH_1964
    -> AttributeManager_50
AttributeManager_38
    ATTR_TABLE = SET_TO archetpye = SFH_65_74
    -> AttributeManager_50
AttributeManager_39
    ATTR_TABLE = SET_TO archetpye = SFH_75_91
    -> AttributeManager_50
AttributeManager_40
    ATTR_TABLE = SET_TO archetpye = SFH_92_05
    -> AttributeManager_50
AttributeManager_41
    ATTR_TABLE = SET_TO archetpye = SFH_06_14
    -> AttributeManager_50
AttributeManager_42
    ATTR_TABLE = SET_TO archetpye = SFH_2015
    -> AttributeManager_50
TestFilter_7
    DEFAULT_VALUE = <UNFILTERED>
    TEST_LIST = "BOOL_OP,OR,COMPOSITE_TEST,""""""<Unused>"""""",TEST_CLAUSE,TEST @Value(constructi) <= 1964",<=1964,"BOOL_OP,OR,COMPOSITE_TEST,""""""<Unused>"""""",TEST_CLAUSE,NUM_TEST @Value(constructi) RANGE [1965,1974]",1965-1974,"BOOL_OP,OR,COMPOSITE_TEST,""""""<Unused>"""""",TEST_CLAUSE,NUM_TEST @Value(constructi) RANGE [1975,1991]",1975-1991,"BOOL_OP,OR,COMPOSITE_TEST,""""""<Unused>"""""",TEST_CLAUSE,NUM_TEST @Value(constructi) RANGE [1992,2005]",1992-2005,"BOOL_OP,OR,COMPOSITE_TEST,""""""<Unused>"""""",TEST_CLAUSE,NUM_TEST @Value(constructi) RANGE [2006,2014]",2006-2014,"BOOL_OP,OR,COMPOSITE_TEST,""""""<Unused>"""""",TEST_CLAUSE,TEST @Value(constructi) >= 2015",>=2015
    <=1964 -> AttributeManager_31
    1965-1974 -> AttributeManager_32
    1975-1991 -> AttributeManager_33
    1992-2005 -> AttributeManager_34
    2006-2014 -> AttributeManager_35
    >=2015 -> AttributeManager_36
AttributeManager_31
    ATTR_TABLE = SET_TO archetpye = MFH_1964
    -> AttributeManager_49
AttributeManager_32
    ATTR_TABLE = SET_TO archetpye = MFH_65_74
    -> AttributeManager_49
AttributeManager_33
    ATTR_TABLE = SET_TO archetpye = MFH_75_91
    -> AttributeManager_49
AttributeManager_34
    ATTR_TABLE = SET_TO archetpye = MFH_92_05
    -> AttributeManager_49
AttributeManager_35
    ATTR_TABLE = SET_TO archetpye = MFH_06_14
    -> AttributeManager_49
AttributeManager_36
    ATTR_TABLE = SET_TO archetpye = MFH_2015
    -> AttributeManager_49
TestFilter_8
    DEFAULT_VALUE = <UNFILTERED>
    TEST_LIST = "BOOL_OP,OR,COMPOSITE_TEST,""""""<Unused>"""""",TEST_CLAUSE,TEST @Value(constructi) <= 1964",<=1964,"BOOL_OP,OR,COMPOSITE_TEST,""""""<Unused>"""""",TEST_CLAUSE,NUM_TEST @Value(constructi) RANGE [1965,1974]",1965-1974,"BOOL_OP,OR,COMPOSITE_TEST,""""""<Unused>"""""",TEST_CLAUSE,NUM_TEST @Value(constructi) RANGE [1975,1991]",1975-1991,"BOOL_OP,OR,COMPOSITE_TEST,""""""<Unused>"""""",TEST_CLAUSE,NUM_TEST @Value(constructi) RANGE [1992,2005]",1992-2005,"BOOL_OP,OR,COMPOSITE_TEST,""""""<Unused>"""""",TEST_CLAUSE,NUM_TEST @Value(constructi) RANGE [2006,2014]",2006-2014,"BOOL_OP,OR,COMPOSITE_TEST,""""""<Unused>"""""",TEST_CLAUSE,TEST @Value(constructi) >= 2015",>=2015
    <=1964 -> AttributeManager_43
    1965-1974 -> AttributeManager_44
    1975-1991 -> AttributeManager_45
    1992-2005 -> AttributeManager_46
    2006-2014 -> AttributeManager_47
    >=2015 -> AttributeManager_48
AttributeManager_43
    ATTR_TABLE = SET_TO archetpye = TH_1964
    -> AttributeManager_11
AttributeManager_44
    ATTR_TABLE = SET_TO archetpye = TH_65_74
    -> AttributeManager_11
AttributeManager_45
    ATTR_TABLE = SET_TO archetpye = TH_75_91
    -> AttributeManager_11
AttributeManager_46
    ATTR_TABLE = SET_TO archetpye = TH_92_05
    -> AttributeManager_11
AttributeManager_47
    ATTR_TABLE = SET_TO archetpye = TH_06_14
    -> AttributeManager_11
AttributeManager_48
    ATTR_TABLE = SET_TO archetpye = TH_2015
    -> AttributeManager_11
Junction_12
    -> TestFilter_9
TestFilter_9
    DEFAULT_VALUE = <UNFILTERED>
    TEST_LIST = "BOOL_OP,OR,COMPOSITE_TEST,""""""<Unused>"""""",TEST_CLAUSE,TEST @Value(constructi) <= 1964",<=1964,"BOOL_OP,OR,COMPOSITE_TEST,""""""<Unused>"""""",TEST_CLAUSE,NUM_TEST @Value(constructi) RANGE [1965,1974]",1965-1974,"BOOL_OP,OR,COMPOSITE_TEST,""""""<Unused>"""""",TEST_CLAUSE,NUM_TEST @Value(constructi) RANGE [1975,1991]",1975-1991,"BOOL_OP,OR,COMPOSITE_TEST,""""""<Unused>"""""",TEST_CLAUSE,NUM_TEST @Value(constructi) RANGE [1992,2005]",1992-2005,"BOOL_OP,OR,COMPOSITE_TEST,""""""<Unused>"""""",TEST_CLAUSE,NUM_TEST @Value(constructi) RANGE [2006,2014]",2006-2014,"BOOL_OP,OR,COMPOSITE_TEST,""""""<Unused>"""""",TEST_CLAUSE,TEST @Value(constructi) >= 2015",>=2015
    <=1964 -> AttributeManager_51
    1965-1974 -> AttributeManager_52
    1975-1991 -> AttributeManager_53
    1992-2005 -> AttributeManager_54
    2006-2014 -> AttributeManager_55
    >=2015 -> AttributeManager_56
AttributeManager_51
    ATTR_TABLE = SET_TO archetpye = Others_1964
    -> AttributeManager_57
AttributeManager_52
    ATTR_TABLE = SET_TO archetpye = Others_65_74
    -> AttributeManager_57
AttributeManager_53
    ATTR_TABLE = SET_TO archetpye = Others_75_91
    -> AttributeManager_57
AttributeManager_54
    ATTR_TABLE = SET_TO archetpye = Others_92_05
    -> AttributeManager_57
AttributeManager_55
    ATTR_TABLE = SET_TO archetpye = Others_06_14
    -> AttributeManager_57
AttributeManager_56
    ATTR_TABLE = SET_TO archetpye = Others_2015
    -> AttributeManager_57

Bookmark: Generalize footprint to simplify geometry
AttributeManager_60
    ATTR_TABLE:
      RENAME_SET_VALUE dwelling_t > dwelling_type
      RENAME_SET_VALUE simplified > simplified_type
      RENAME_SET_VALUE constructi > construction_year
      RENAME_SET_VALUE residentia > residential
      RENAME_SET_VALUE gebruiksdo > b_function
      RENAME_SET_VALUE oppervlakt > b_Area
      RENAME_SET_VALUE aantal_ver > address_num
      RENAME_SET_VALUE Number_of_ > adjacent_b_num
      REMOVE pandidenti
      RENAME_SET_VALUE est_occupa > est_b_occupants
      RENAME_SET_VALUE pc6_aantal > pc6_population
      RENAME_SET_VALUE pc6_reside > pc6_r_area
      RENAME_SET_VALUE dataComple > dataComplete
      RENAME_SET_VALUE building_r > building_r_area
      RENAME_SET_VALUE archetpye > archetype
    -> Generalizer_2
Generalizer_2
    ALG_TEXT = Douglas (Generalize)
    CLEANING_TOLERANCE = Automatic
    PRESERVE = Yes
    PRESERVE_PATHS = No
    TOLERANCE = 0.5
    -> Clipper_9 [CLIPPEE]
    -> BuildingBase_generalized (writer ESRISHAPE_17)

Bookmark: Examine pc6 energy data usability
Test_PC6_resgion: TestFilter
    DEFAULT_VALUE = <UNFILTERED>
    TEST_LIST = "BOOL_OP,OR,COMPOSITE_TEST,""""""<Unused>"""""",TEST_CLAUSE,TEST @Value(postcode_from) = @Value(postcode_to)",consistentPC6
    consistentPC6 -> TestFilter_11
TestFilter_11
    DEFAULT_VALUE = <UNFILTERED>
    TEST_LIST:
      "BOOL_OP,AND,COMPOSITE_TEST,""""""<Unused>"""""",TEST_CLAUSE,TEST @Value(physical_status_perc) = 100
      TEST @Value(deliver_direction_perc) = 100",FullDelivery
    FullDelivery -> AttributeKeeper
AttributeKeeper
    KEEP_ATTRS = connections_num,avg_annual_consumption,postcode_to
    -> FeatureMerger_4 [SUPPLIER]
TestFilter_10
    DEFAULT_VALUE = <UNFILTERED>
    TEST_LIST = "BOOL_OP,OR,COMPOSITE_TEST,""""""<Unused>"""""",TEST_CLAUSE,TEST @Value(dataComple) = 1",simulatedBuildings
    simulatedBuildings -> AttributeKeeper_3
    <UNFILTERED> -> NotSimulated
AttributeKeeper_3
    KEEP_ATTRS = buildingID,address_nu,volume,dataComple,postcodes,b_Area
    -> Aggregator_4
Aggregator_4
    ACCUM_ATTRS_NAME = Use Attributes From One Feature
    AGGREGATE_TYPE = Homogeneous Collection (If Possible)
    GROUP_BY = postcodes
    MODE = Geometry - Assemble One Level
    ORDERED = No
    SEP = ,
    SUM = address_nu
    AGGREGATE -> FeatureMerger_4 [REQUESTOR]
FeatureMerger_4
    ATTR_ACCUM_MODE = Merge Supplier
    ATTR_CONFLICT_RES = Use Requestor
    IGNORE_NULLS = No
    JOIN_KEYS = @Value(postcodes) @Value(postcode_to) AUTO
    MERGE_TYPE = Attributes Only
    PROCESS_DUPS = NO
    REJECT_NULL_MISSING_KEYS = No
    SUPPLIERS_FIRST = No
    MERGED -> TestFilter_12
    UNMERGED_REQUESTOR -> EnergyDataNotQualified
TestFilter_12
    DEFAULT_VALUE = NumNotMatched
    TEST_LIST = "BOOL_OP,OR,COMPOSITE_TEST,""""""<Unused>"""""",TEST_CLAUSE,TEST @Value(address_nu) = @Value(connections_num)",matchedConnectionNum,"BOOL_OP,OR,COMPOSITE_TEST,""""""<Unused>"""""",TEST_CLAUSE,TEST @abs(@sub(@Value(address_nu),@Value(connections_num))) <= 1",Candidates
    matchedConnectionNum -> AttributeManager_59
    Candidates -> AttributeManager_59
    NumNotMatched -> NumNotMatched
AttributeManager_59
    ATTR_TABLE:
      RENAME_SET_VALUE avg_annual_consumption > avg_consumption_yr_17
      SET_TO Comparable_17 = 1
      SET_TO ConnDif = @sub(@Value(address_nu),@Value(connections_num))
    -> AttributeKeeper_2
AttributeKeeper_2
    KEEP_ATTRS = avg_consumption_yr_17,address_nu,postcodes,ConnDif
    -> Candidates
    -> FeatureMerger_7 [SUPPLIER]
NumNotMatched: Inspector [off]
EnergyDataNotQualified: Inspector [off]
NotSimulated: Inspector [off]

Bookmark: Crop and experiment with small area
Note: Crop to allow GH capable of reading smaller shp. file
Clipper_9
    ATTR_ACCUM_MODE = Merge Clipper
    ATTR_CONFLICT_RES = Use Clippee
    BOUNDARY_CASES = Treat as Inside
    CLEANING_TOLERANCE = None
    CLIPPED_ATTR = _clipped
    CLIP_TYPE = Multiple Clippers
    CONNECT_Z_MODE = First Wins
    CREATE_AGGREGATES = Yes
    LINES_AS_SEGMENTS = No
    MEASURE_TYPE = Continuous
    MISSING_VAL_MODE = Compute
    PRESERVE_CLIPPEE_EXTENTS = No
    VAL_SOURCE = Clippee Only
    INSIDE -> BuildingBase_small_generalized (writer ESRISHAPE_16)
    INSIDE -> BuildingBaselayer (writer POSTGRES_3)

Bookmark: Merge meterd data and simulation results into one table
FeatureMerger_15
    ATTR_ACCUM_MODE = Merge Supplier
    ATTR_CONFLICT_RES = Use Requestor
    IGNORE_NULLS = No
    JOIN_KEYS = @Value(buildingID) @Value(buildingID) AUTO
    MERGE_TYPE = Attributes Only
    PROCESS_DUPS = NO
    REJECT_NULL_MISSING_KEYS = No
    SUPPLIERS_FIRST = No
    MERGED -> FeatureMerger_16 [SUPPLIER]
FeatureMerger_16
    ATTR_ACCUM_MODE = Merge Supplier
    ATTR_CONFLICT_RES = Use Requestor
    IGNORE_NULLS = No
    JOIN_KEYS = @Value(buildingID) @Value(buildingID) AUTO
    MERGE_TYPE = Attributes Only
    PROCESS_DUPS = NO
    REJECT_NULL_MISSING_KEYS = No
    SUPPLIERS_FIRST = No
    MERGED -> AttributeKeeper_5
AttributeKeeper_5
    KEEP_ATTRS = case15_annual_h_wh,case24_annual_h_wh,case10_annual_h_wh,case12_annual_h_wh,case19_annual_h_wh,address_nu,postcodes,case22_annual_h_wh,case4_annual_h_wh,case17_annual_h_wh,case20_annual_h_wh,case23_annual_h_wh,case14_annual_h_wh,case13_annual_h_wh,case7_annual_h_wh,case8_annual_h_wh,case2_annual_h_wh,volume_CitySim,case25_annual_h_wh,case16_annual_h_wh,case21_annual_h_wh,avg_consumption_yr_17,case1_annual_h_wh,case5_annual_h_wh,case11_annual_h_wh,case18_annual_h_wh,case3_annual_h_wh,case9_annual_h_wh,case6_annual_h_wh
    -> Aggregator_5
Aggregator_5
    ACCUM_ATTRS_NAME = Use Attributes From One Feature
    AGGREGATE_TYPE = Homogeneous Collection (If Possible)
    GROUP_BY = postcodes
    MODE = Geometry - Assemble One Level
    ORDERED = No
    SEP = ,
    SUM = case15_annual_h_wh case24_annual_h_wh case10_annual_h_wh case12_annual_h_wh case19_annual_h_wh address_nu case22_annual_h_wh case4_annual_h_wh case17_annual_h_wh case20_annual_h_wh case23_annual_h_wh case14_annual_h_wh case13_annual_h_wh case7_annual_h_wh case8_annual_h_wh case2_annual_h_wh volume_CitySim case25_annual_h_wh case16_annual_h_wh case21_annual_h_wh case1_annual_h_wh case5_annual_h_wh case11_annual_h_wh case18_annual_h_wh case3_annual_h_wh case9_annual_h_wh case6_annual_h_wh
    AGGREGATE -> AttributeManager_64
AttributeManager_64
    ATTR_TABLE = SET_TO pc6_consumption_Wh = @mult(@Value(address_nu),@Value(avg_consumption_yr_17),1.02264,39.2,0.27778,1000)
    -> AttributeCreator_4
    -> Inspector_6
AttributeCreator_4
    ATTR_TABLE:
      SET_TO pc6_kWh_m3 = @div(@mult(@Value(pc6_consumption_Wh),0.001),@Value(volume_CitySim))
      SET_TO case1_annual_h_kWh_m3 = @div(@mult(@Value(case1_annual_h_wh),0.001),@Value(volume_CitySim))
      SET_TO case2_annual_h_kWh_m3 = @div(@mult(@Value(case2_annual_h_wh),0.001),@Value(volume_CitySim))
      SET_TO case3_annual_h_kWh_m3 = @div(@mult(@Value(case3_annual_h_wh),0.001),@Value(volume_CitySim))
      SET_TO case4_annual_h_kWh_m3 = @div(@mult(@Value(case4_annual_h_wh),0.001),@Value(volume_CitySim))
      SET_TO case5_annual_h_kWh_m3 = @div(@mult(@Value(case5_annual_h_wh),0.001),@Value(volume_CitySim))
    -> Inspector_5

Bookmark: Join property and accommodation
AttributeManager_3
    ATTR_TABLE:
      REMOVE gml_parent_id
      REMOVE gml_parent_property
      RENAME_SET_VALUE gml_id
      RENAME_SET_VALUE identificatie
      REMOVE identificatie.xsi_nil
      RENAME_SET_VALUE oppervlakte
      REMOVE oppervlakte.xsi_nil
      RENAME_SET_VALUE status
      REMOVE status.xsi_nil
      RENAME_SET_VALUE gebruiksdoel
      REMOVE gebruiksdoel.xsi_nil
      RENAME_SET_VALUE openbare_ruimte
      REMOVE openbare_ruimte.xsi_nil
      RENAME_SET_VALUE huisnummer
      REMOVE huisnummer.xsi_nil
      RENAME_SET_VALUE huisletter
      REMOVE huisletter.xsi_nil
      RENAME_SET_VALUE toevoeging
      REMOVE toevoeging.xsi_nil
      REMOVE postcode.xsi_nil
      REMOVE woonplaats.xsi_nil
      REMOVE actualiteitsdatum.xsi_nil
      REMOVE bouwjaar.xsi_nil
      REMOVE pandidentificatie.xsi_nil
      REMOVE pandstatus.xsi_nil
    -> FeatureMerger [REQUESTOR]
VolumeCalculator
    MULT = 1
    SET_TRAIT = No
    VOLUME_ATTR = _volume
    -> AttributeManager
AttributeManager
    ATTR_TABLE:
      REMOVE gml_parent_id
      REMOVE gml_parent_property
      REMOVE identificatie.xsi_nil
      RENAME_SET_VALUE bouwjaar > construction_year
      REMOVE bouwjaar.xsi_nil
      REMOVE status.xsi_nil
      RENAME_SET_VALUE gebruiksdoel > intendeduse
      REMOVE gebruiksdoel.xsi_nil
      RENAME_SET_VALUE oppervlakte_min > surface_min
      REMOVE oppervlakte_min.xsi_nil
      RENAME_SET_VALUE oppervlakte_max > surface_max
      REMOVE oppervlakte_max.xsi_nil
      RENAME_SET_VALUE aantal_verblijfsobjecten > number_of_dwellings
      REMOVE aantal_verblijfsobjecten.xsi_nil
      REMOVE actualiteitsdatum.xsi_nil
      REMOVE _clipped
      REMOVE fme_basename
      REMOVE z.median
      RENAME_SET_VALUE _volume > volume
    -> FeatureMerger [SUPPLIER]
FeatureMerger
    ATTR_ACCUM_MODE = Prefix Supplier
    CLEANING_TOLERANCE = None
    CONNECT_Z_MODE = First Wins
    GEOM_TYPE = Build Polygons
    IGNORE_NULLS = No
    JOIN_KEYS = @Value(pandidentificatie) @Value(identificatie) AUTO
    MERGE_TYPE = Attributes Only
    PROCESS_DUPS = Yes
    REJECT_NULL_MISSING_KEYS = No
    SUPPLIERS_FIRST = No
    SUPPLIER_PREFIX = pand_
    MERGED -> AttributeManager_2
AttributeManager_2
    ATTR_TABLE:
      RENAME_SET_VALUE identificatie > addressID
      RENAME_SET_VALUE oppervlakte > surface
      RENAME_SET_VALUE gebruiksdoel > function
      RENAME_SET_VALUE bouwjaar > construction_year
      RENAME_SET_VALUE openbare_ruimte > public_space
      RENAME_SET_VALUE huisnummer > house_number
      RENAME_SET_VALUE huisletter > house_letter
      RENAME_SET_VALUE toevoeging > house_addition
      RENAME_SET_VALUE woonplaats > municipality
      REMOVE actualiteitsdatum
      RENAME_SET_VALUE pand_identificatie > buildingID
      RENAME_SET_VALUE pand_gml_id > building_gml_id
      REMOVE pandidentificatie
      REMOVE pandstatus
      RENAME_SET_VALUE pand_construction_year > building_construction_year
      RENAME_SET_VALUE pand_status > building_status
      RENAME_SET_VALUE pand_intendeduse > building_function
      RENAME_SET_VALUE pand_volume > building_volume
      RENAME_SET_VALUE pand_surface_min > building_surface_min
      RENAME_SET_VALUE pand_surface_max > building_surface_max
      RENAME_SET_VALUE pand_number_of_dwellings > building_number_of_dwellings
      REMOVE geometrie
      REMOVE pandgeometrie
      REMOVE _clipped
      REMOVE pand_actualiteitsdatum
      REMOVE pand_geometrie
    -> Inspector_7
    -> AccommodationBuilding_training (writer CSV2_2)
    -> Junction
Note: DuplicateFilter : Input
Junction
    -> Junction_2
    -> Dissolver

Bookmark: Processing
Note: First execute this step, then clean and integrate in PostgreSQL DB
Dissolver [off]
    ACCUM_INPUT_ATTRS = Use Attributes From One Feature
    CONNECT_Z_MODE = First Wins
    DEAGGREGATE_INPUT = Yes
    GROUP_BY = postcode
    NO_OVRLP = No
    AREA -> AttributeExposer
Note: Second step to generate building model
AttributeExposer [off]
    ATTR_LIST = postcode
    -> Inspector_2
    -> pc6_training (writer GML_6)
SimulatedBuildings: Aggregator [off]
    ACCUM_ATTRS_NAME = Use Attributes From One Feature
    AGGREGATE_TYPE = Homogeneous Collection (If Possible)
    GROUP_BY = gml_id _geometry_name geometrie sketchup_layer_name
    MODE = Geometry - Assemble One Level
    ORDERED = No
    SEP = ,
    AGGREGATE -> GeometryColorSetter
    AGGREGATE -> AMS_Simulated_training (writer SKP_1)
    AGGREGATE -> Inspector_4
GeometryColorSetter [off]
    ALPHA = 1
    FILL_COLOR = 1,0.505882,0.0117647
    MODE = Fixed
    REC = Yes
    SIDE = Both
    COLORED -> AttributeCreator_3
AttributeCreator_3 [off]
    ATTR_TABLE = SET_TO simulated = 1
    -> AMS_SimuPlusRest (writer SKP_3)
CompletedModel: Aggregator
    ACCUM_ATTRS_NAME = Use Attributes From One Feature
    AGGREGATE_TYPE = Homogeneous Collection (If Possible)
    GROUP_BY = gml_id _geometry_name geometrie sketchup_layer_name
    MODE = Geometry - Assemble One Level
    ORDERED = No
    SEP = ,
    AGGREGATE -> TestFilter
    AGGREGATE -> AMS_Complete_training (writer SKP_2)
    AGGREGATE -> Inspector
TestFilter
    DEFAULT_VALUE = <UNFILTERED>
    TEST_LIST = "BOOL_OP,OR,COMPOSITE_TEST,""""""<Unused>"""""",TEST_CLAUSE,TEST @Value(buildingID) != @Value(BuildingID)",@Value(buildingID) != @Value(BuildingID)
    @Value(buildingID) != @Value(BuildingID) -> AttributeCreator_2
AttributeCreator_2
    ATTR_TABLE = SET_TO simulated = 0
    -> AMS_SimuPlusRest (writer SKP_3)
GeometryColorSetter_2 [off]
    ALPHA = 0.7
    FILL_COLOR = 1,1,1
    MODE = Fixed
    REC = Yes
    SIDE = Both
    COLORED -> Inspector_16

Bookmark: Export geometry to skp.
Junction_2
    -> DuplicateFilter
DuplicateFilter
    INPUT_ORDERED_CHOICE = No
    KEYATTR = buildingID
    UNIQUE -> FeatureMerger_5 [REQUESTOR]
AttributeManager_6
    ATTR_TABLE = RENAME_SET_VALUE identificatie > sketchup_layer_name
    -> FeatureMerger_5 [SUPPLIER]
FeatureMerger_5
    ATTR_ACCUM_MODE = Merge Supplier
    ATTR_CONFLICT_RES = Use Requestor
    CLEANING_TOLERANCE = None
    IGNORE_NULLS = No
    JOIN_KEYS = @Value(buildingID) @Value(sketchup_layer_name) AUTO
    MERGE_TYPE = Attributes and Geometry
    PROCESS_DUPS = No
    REJECT_NULL_MISSING_KEYS = No
    SUPPLIERS_FIRST = No
    MERGED -> GeometryPropertySetter
GeometryPropertySetter
    OVERWRITE_CHOICE = Yes
    REMOVE_ATTRIBUTE = No
    SETTYPE_PARAM = Traits From Attributes
    SRC_ATTRS = sketchup_layer_name
    SET -> Deaggregator
Deaggregator
    ATTR_ACCUM_MODE = Merge List Attributes
    ATTR_CONFLICT_RES = Use List Attribute Values
    CHILD_ID_ATTR = _hierarchy_child_id_list
    COPY_ATTR = Every Node
    EXPLODE_INSTANCES = No
    GEOM_NAME_FIELD = _geometry_name
    ID_ATTR = _hierarchy_id
    ID_SELECTION = ID and Parent ID
    LIST_ATTR_MODE_LOOKUP = LEAN
    MODE = Flatten One Level
    PARENT_ID_ATTR = _hierarchy_parent_id
    PART_NUMBER_FIELD = _part_number
    SPLIT_COMPOSITES = No
    DEAGGREGATED -> FeatureMerger_6 [REQUESTOR]
FeatureMerger_6
    ATTR_ACCUM_MODE = Merge Supplier
    ATTR_CONFLICT_RES = Use Requestor
    CLEANING_TOLERANCE = None
    IGNORE_NULLS = No
    JOIN_KEYS = @Value(buildingID) @Value(BuildingID) AUTO
    MERGE_TYPE = Attributes and Geometry
    PROCESS_DUPS = No
    REJECT_NULL_MISSING_KEYS = No
    SUPPLIERS_FIRST = No
    MERGED -> SimulatedBuildings
    MERGED -> CompletedModel
    MERGED -> 2DForcer [off]
    MERGED -> ModelwGround [off]
    UNMERGED_REQUESTOR -> CompletedModel

Bookmark: Building + Ground
2DForcer [off]
    2D -> Clipper_3 [CLIPPER]
Clipper_3 [off]
    BOUNDARY_CASES = Treat as Inside
    CLEANING_TOLERANCE = None
    CLIPPED_ATTR = _clipped
    CLIP_TYPE = Multiple Clippers
    CONNECT_Z_MODE = Average
    CREATE_AGGREGATES = Yes
    LINES_AS_SEGMENTS = No
    MEASURE_TYPE = Continuous
    MISSING_VAL_MODE = Compute
    PRESERVE_CLIPPEE_EXTENTS = No
    VAL_SOURCE = Clipper and Clippee
    OUTSIDE -> Deaggregator_3
Deaggregator_3 [off]
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> AttributeCreator
AttributeCreator [off]
    ATTR_TABLE = SET_TO sketchup_layer_name = GROUND
    -> GeometryPropertySetter_2
GeometryPropertySetter_2 [off]
    OVERWRITE_CHOICE = Yes
    REMOVE_ATTRIBUTE = No
    SETTYPE_PARAM = Traits From Attributes
    SRC_ATTRS = sketchup_layer_name
    SET -> ModelwGround
ModelwGround: Aggregator [off]
    ACCUM_ATTRS_NAME = Use Attributes From One Feature
    AGGREGATE_TYPE = Homogeneous Collection (If Possible)
    GROUP_BY = sketchup_layer_name
    MODE = Geometry - Assemble One Level
    ORDERED = No
    SEP = ,
    AGGREGATE -> GeometryColorSetter_2
